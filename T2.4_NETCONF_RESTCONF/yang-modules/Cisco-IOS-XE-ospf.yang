module Cisco-IOS-XE-ospf {
  namespace "http://cisco.com/ns/yang/Cisco-IOS-XE-ospf";
  prefix ios-ospf;

  import cisco-semver {
    prefix cisco-semver;
  }
  import ietf-inet-types {
    prefix inet;
  }
  import Cisco-IOS-XE-types {
    prefix ios-types;
  }
  import Cisco-IOS-XE-native {
    prefix ios;
  }
  import Cisco-IOS-XE-features {
    prefix ios-features;
  }
  import Cisco-IOS-XE-isis {
    prefix ios-isis;
  }
  include Cisco-IOS-XE-ospf-obsolete;

  organization
    "Cisco Systems, Inc.";
  contact
    "Cisco Systems, Inc.
     Customer Service
     
     Postal: 170 W Tasman Drive
     San Jose, CA 95134
     
     Tel: +1 1800 553-NETS
     
     E-mail: cs-yang@cisco.com";
  description
    "Cisco XE Native Open Shortest Path First (OSPF) Yang model.
     Copyright (c) 2016-2020 by Cisco Systems, Inc.
     All rights reserved.";

  revision 2021-03-01 {
    description
      "- Add support for affinity, flex-algo and affinity-map";
  }
  revision 2020-11-01 {
    description
      "- Old model marked obsolete
       - Addition of ospf packet-size command";
  }
  revision 2020-07-01 {
    description
      "Addition of delay normalize command for ospf interface";
  }
  revision 2020-03-01 {
    description
      "- Change order of virtual-link topology";
  }
  revision 2019-11-01 {
    description
      "- Added default information originate config";
    cisco-semver:module-version "2.0.0";
  }
  revision 2019-07-01 {
    description
      "- Establish semantic version baseline
       - Deprecate old model
       - Add ospf support for BD-VIF interface";
    cisco-semver:module-version "1.0.0";
  }
  revision 2019-01-22 {
    description
      "Added leaf for App-hosting Gigabit Ethernet interface";
  }
  revision 2018-11-07 {
    description
      "Cleanup spelling errors in description statements";
  }
  revision 2018-10-31 {
    description
      "Add ipv6 eigrp command under interface";
  }
  revision 2018-09-07 {
    description
      "Add must constraint to ospf with vrf, on vrf address-family";
  }
  revision 2018-07-31 {
    description
      "Adding augmented code for BDI and vlan interface";
  }
  revision 2018-07-26 {
    description
      "removed redistribute bgp must constraint on vrf/definition/rd";
  }
  revision 2018-07-10 {
    description
      "Add .* to cli-preformatted, apply input validation to disallow new lines";
  }
  revision 2018-06-28 {
    description
      "Added must constraints for deleting vrf, changing switchport from no switchport";
  }
  revision 2018-06-13 {
    description
      "Adding augmented code for Dialer interface";
  }
  revision 2018-05-31 {
    description
      "change ip ospf id to type leafref under an interface";
  }
  revision 2018-05-21 {
    description
      "Add 'cli-preformatted' to leaf auth-key";
  }
  revision 2018-01-19 {
    description
      "fix issue in redistribute maximum-prefix <number> <threshold> warning-only";
  }
  revision 2017-12-11 {
    description
      "Add support for redistribute nat-route dia/outside";
  }
  revision 2017-11-27 {
    description
      "Added Change 25GE name";
  }
  revision 2017-11-16 {
    description
      "fix area 0 range <ipv4> <ipv4-mask> issue";
  }
  revision 2017-11-14 {
    description
      "Add 40 and 100GE interface";
  }
  revision 2017-10-24 {
    description
      "Add table-map support";
  }
  revision 2017-10-20 {
    description
      "To allow support of ip osfp authentication-key <string> under interface";
  }
  revision 2017-10-10 {
    description
      "Added redistribute omp support";
  }
  revision 2017-08-18 {
    description
      "This revision has changes for new 5gig and 25gig interfaces addition";
  }
  revision 2017-08-15 {
    description
      "add full nsf support and ospf support for BDI interfaces";
  }
  revision 2017-04-28 {
    description
      "inet:ipv6-prefix changed to ios-types:ipv6-prefix";
  }
  revision 2017-03-28 {
    description
      "Added NED Yang Data Model support for MPLS-TE";
  }
  revision 2017-02-07 {
    description
      "Initial revision";
  }

  grouping config-ospf-adjacency-grouping {
    container adjacency {
      description
        "Control adjacency formation";
      container stagger {
        description
          "Stagger adjacency formation";
        leaf min-adjacencies {
          description
            "Initial number of adjacencies allowed to be forming in an area";
          type union {
            type uint32 {
              range "1..65535";
            }
            type enumeration {
              enum "none";
            }
          }
          default "300";
        }
        leaf max-adjacencies {
          description
            "Maximum number of adjacencies allowed to be forming";
          type uint32 {
            range "1..65535";
          }
          default "300";
        }
      }
    }
  }

  grouping config-ospf-packet-size-grouping {
    leaf packet-size {
      description
        "OSPF Packet Size";
      type uint32 {
        range "576..10000";
      }
    }
  }

  grouping config-ospf-area-grouping {
    list area {
      description
        "OSPF area parameters";
      key "area-id";
      leaf area-id {
        description
          "OSPF area ID";
        type ios-types:ospf-area-type;
        must "../authentication or ../capability or ../default-cost or ../filter-list or ../ipv4-range or ../nssa or ../sham-link or ../stub or ../virtual-link";
      }
      container authentication {
        description
          "Enable authentication";
        presence "true";
        leaf message-digest {
          description
            "Use message-digest authentication";
          type empty;
        }
      }
      container capability {
        description
          "Enable area specific capability";
        leaf default-exclusion {
          description
            "Enable exclusion of links from base topology";
          type empty;
        }
      }
      leaf default-cost {
        description
          "Set the summary default-cost of a NSSA/stub area";
        type uint32 {
          range "0 .. 16777214";
        }
      }
      uses config-ospf-area-filter-list-grouping;
      uses config-ospf-area-nssa-grouping;
      uses config-ospf-area-range-grouping;
      uses config-ospf-area-sham-link-grouping;
      uses config-ospf-area-stub-grouping;
      uses config-ospf-area-virtual-link-grouping;
      uses config-ospf-packet-size-grouping;
    }
  }

  grouping config-ospf-area-filter-list-grouping {
    list filter-list {
      description
        "Filter networks between OSPF areas";
      key "in-out";
      leaf in-out {
        type enumeration {
          enum "in";
          enum "out";
        }
      }
      leaf prefix {
        description
          "Filter prefixes between OSPF areas";
        type string;
      }
    }
  }

  grouping config-ospf-area-nssa-grouping {
    container nssa {
      description
        "Specify a NSSA area";
      presence "true";
      when "../ios-ospf:area-id != 0";
      must "not (../ios-ospf:stub)" {
        error-message "area configured as STUB";
      }
      container nssa-options {
        leaf no-redistribution {
          description
            "No redistribution into this NSSA area";
          type empty;
        }
        container default-information-originate {
          description
            "Originate Type 7 default into NSSA area";
          presence "true";
          leaf metric {
            description
              "OSPF default metric";
            type int32 {
              range "0 .. 16777214";
            }
          }
          leaf metric-type {
            description
              "OSPF metric type for default routes";
            type ios-types:ospf-metric-type;
          }
        }
        leaf no-summary {
          description
            "Do not send summary LSA into NSSA";
          type empty;
        }
        leaf no-ext-capability {
          description
            "Do not send domain specific capabilities into NSSA";
          type empty;
        }
      }
      container translate {
        description
          "Translate LSA";
        container type7 {
          description
            "From Type 7 to Type 5";
          leaf always {
            description
              "Always translate LSAs on this ABR";
            type empty;
          }
          leaf suppress-fa {
            description
              "Suppress forwarding address in translated LSAs";
            type empty;
          }
        }
      }
    }
  }

  grouping config-ospf-area-range-grouping {
    container ipv4-range {
      list range {
        description
          "Summarize routes matching address/mask (border routers only)";
        key "ip mask";
        leaf ip {
          description
            "IP address to match";
          type inet:ipv4-address;
        }
        leaf mask {
          description
            "IP mask for address";
          type inet:ipv4-address;
        }
        leaf advertise-not-advertise {
          description
            "advertise/not-advertise";
          type enumeration {
            enum "advertise";
            enum "not-advertise";
          }
          default "advertise";
        }
        leaf cost {
          description
            "User specified metric for this range";
          type uint32 {
            range "0 .. 16777214";
          }
        }
      }
    }
  }

  grouping config-ospf-area-sham-link-grouping {
    list sham-link {
      description
        "Define a sham link and its parameters";
      key "source dest";
      leaf source {
        description
          "IP addr associated with sham-link source";
        type inet:ip-address;
      }
      leaf dest {
        description
          "IP addr associated with sham-link destination";
        type inet:ip-address;
      }
      leaf cost {
        description
          "Associate a cost with the sham-link";
        type uint16 {
          range "1 .. 65535";
        }
      }
      container ttl-security {
        description
          "TTL security check";
        leaf hops {
          description
            "IP hops";
          type uint8 {
            range "1..254";
          }
        }
      }
    }
  }

  grouping config-ospf-area-stub-grouping {
    container stub {
      description
        "Specify a stub area";
      presence "true";
      when "../ios-ospf:area-id != 0";
      must "not (../ios-ospf:nssa)" {
        error-message "area configured as NSSA";
      }
      leaf no-summary {
        description
          "Do not send summary LSA into stub area";
        type empty;
      }
      leaf no-ext-capability {
        description
          "Do not send domain specific capabilities into stub area";
        type empty;
      }
    }
  }

  grouping config-ospf-area-virtual-link-grouping {
    list virtual-link {
      description
        "Define a virtual link and its parameters";
      key "id";
      leaf id {
        description
          "ID (IP addr) associated with virtual link neighbor";
        type inet:ip-address;
      }
      container retransmit-interval {
        description
          "LSA retransmit interval";
        leaf retransmit-interval-value {
          description
            "Seconds";
          type uint16 {
            range "1 .. 8192";
          }
          units "seconds";
          default "5";
        }
      }
      container transmit-delay {
        description
          "LSA transmission delay";
        leaf transmit-delay-value {
          description
            "Seconds";
          type uint16 {
            range "1 .. 8192";
          }
          units "seconds";
          default "1";
        }
      }
      container hello-interval {
        description
          "Hello packet interval";
        leaf hello-interval-value {
          description
            "Seconds";
          type int16 {
            range "1 .. 8192";
          }
          units "seconds";
          default "10";
        }
      }
      container dead-interval {
        description
          "Dead router detection time";
        leaf dead-interval-value {
          description
            "Seconds";
          type uint16 {
            range "1 .. 8192";
          }
          units "seconds";
          default "40";
        }
      }
      container ttl-security {
        description
          "TTL security check";
        leaf hops {
          description
            "IP hops";
          type uint8 {
            range "1..254";
          }
        }
      }
      container authentication {
        description
          "Set authentication type";
        choice auth-type-choice {
          default "clear-text";
          leaf key-chain {
            description
              "Use a key-chain for cryptographic authentication keys";
            type string;
          }
          leaf message-digest {
            description
              "Message-digest authentication";
            type empty;
          }
          leaf null {
            description
              "No authentication";
            type empty;
          }
          leaf clear-text {
            type empty;
          }
        }
      }
      container topology {
        description
          "Disable virtual link on topology";
        leaf disable {
          description
            "Disable virtual link";
          type empty;
        }
      }
      container authentication-key {
        description
          "Set authentication key";
        leaf auth-type {
          description
            "Encryption type (0 for not yet encrypted, 7 for proprietary)";
          type uint8 {
            range "0 .. 7";
          }
        }
        leaf auth-key {
          description
            "Authentication key (8 chars)";
          type string {
            length "1 .. 8";
          }
        }
      }
      uses config-ospf-message-digest-key-grouping;
    }
  }

  grouping config-ospf-auto-cost-grouping {
    container auto-cost {
      description
        "Calculate OSPF interface cost according to bandwidth";
      leaf reference-bandwidth {
        description
          "Use reference bandwidth method to assign OSPF cost";
        type uint32 {
          range "1 .. 4294967";
        }
        default "100";
      }
    }
  }

  grouping config-ospf-autoroute-exclude-grouping {
    container autoroute-exclude {
      description
        "Exclude using tunnel path for certain prefixes";
      leaf prefix-list {
        description
          "Filter prefixes";
        type string;
      }
    }
  }

  grouping config-ospf-bfd-grouping {
    container bfd {
      description
        "BFD configuration commands";
      container all-interfaces {
        description
          "Enable BFD on all interfaces";
        presence "true";
        leaf strict-mode {
          description
            "Enable BFD in strict mode";
          type empty;
        }
      }
    }
  }

  grouping config-ospf-capability-common-grouping {
    leaf lls {
      description
        "Link-local Signaling (LLS) support";
      type boolean;
      default "true";
    }
    leaf opaque {
      description
        "Opaque LSA";
      type boolean;
      default "true";
    }
    leaf transit {
      description
        "Transit Area";
      type boolean;
      default "true";
    }
  }

  grouping config-ospf-capability-vrf-lite-grouping {
    leaf vrf-lite {
      description
        "Do not perform PE specific checks";
      type boolean;
      default "false";
    }
  }

  grouping config-ospf-capability-grouping {
    container capability {
      description
        "Enable specific OSPF feature";
      uses config-ospf-capability-common-grouping;
    }
  }

  grouping config-ospf-capability-vrf-grouping {
    container capability {
      description
        "Enable specific OSPF feature";
      uses config-ospf-capability-common-grouping;
      uses config-ospf-capability-vrf-lite-grouping;
    }
  }

  grouping config-ospf-compatible-grouping {
    container compatible {
      description
        "OSPF compatibility list";
      leaf rfc1583 {
        description
          "Compatible with RFC 1583";
        type boolean;
        default "true";
      }
      leaf rfc1587 {
        description
          "Compatible with RFC 1587";
        type boolean;
        default "false";
      }
      leaf rfc5243 {
        description
          "Compatible with RFC 5243";
        type boolean;
        default "true";
      }
    }
  }

  grouping config-ospf-default-information-grouping {
    container default-information {
      description
        "Control distribution of default information";
      container originate {
        description
          "Distribute a default route";
        presence "true";
        leaf always {
          description
            "Always advertise default route";
          type empty;
        }
        leaf metric {
          description
            "OSPF default metric";
          type uint32 {
            range "0 .. 16777214";
          }
        }
        leaf metric-type {
          description
            "OSPF metric type for default routes";
          type ios-types:ospf-metric-type;
        }
        leaf route-map {
          description
            "Route map reference";
          type string;
        }
      }
    }
  }

  grouping config-ospf-default-metric-grouping {
    leaf default-metric {
      description
        "Set metric of redistributed routes";
      type uint32 {
        range "1 .. 16777214";
      }
      default "20";
    }
  }

  grouping config-ospf-domain-id-grouping {
    container domain-id {
      description
        "OSPF domain-id";
      choice domain-id-choice {
        container ip-format-secondary {
          leaf ip {
            type inet:ipv4-address;
          }
          list ip-secondary {
            key "ip secondary";
            leaf ip {
              must "../../ip";
              type inet:ipv4-address;
            }
            leaf secondary {
              description
                "Secondary Domain-ID";
              type enumeration {
                enum "secondary";
              }
            }
          }
          leaf secondary {
            status obsolete;
            description
              "Secondary Domain-ID";
            type empty;
          }
        }
        leaf null {
          description
            "null Domain-ID";
          type empty;
        }
        container type {
          description
            "OSPF domain ID type in Hex format";
          leaf type-leaf {
            type enumeration {
              enum "0005";
              enum "0105";
              enum "0205";
              enum "8005";
            }
          }
          leaf value {
            description
              "OSPF domain ID value in Hex format";
            type string {
              pattern "[0-9a-fA-F]{12}";
            }
          }
          leaf secondary {
            description
              "Secondary Domain-ID";
            type empty;
          }
        }
      }
    }
  }

  grouping config-ospf-domain-tag-grouping {
    leaf domain-tag {
      description
        "OSPF domain-tag";
      type uint32 {
        range "1 .. 4294967295";
      }
    }
  }

  grouping config-ospf-discard-route-grouping {
    container discard-route-external-internal {
      description
        "Enable or disable discard-route installation";
      leaf discard-route {
        description
          "Enable or disable discard-route installation";
        type boolean;
        default "true";
      }
      leaf external {
        description
          "Discard route for redistributed summarised routes";
        must "../discard-route";
        type uint32 {
          range "1 .. 255";
        }
        default "254";
      }
      leaf internal {
        description
          "Discard route for summarised internal routes";
        must "../discard-route";
        type uint32 {
          range "1 .. 255";
        }
        default "110";
      }
    }
  }

  grouping config-ospf-distance-grouping {
    container distance {
      description
        "Define an administrative distance";
      leaf distance {
        description
          "Administrative distance";
        type uint32 {
          range "1 .. 255";
        }
        default "110";
      }
      list distance-ip-wildcard {
        key "ip wildcard";
        leaf distance {
          description
            "Administrative distance";
          type uint32 {
            range "1 .. 255";
          }
        }
        leaf ip {
          type inet:ipv4-address;
        }
        leaf wildcard {
          type inet:ipv4-address;
        }
        leaf acl-name {
          type ios-types:access-list-standard-id-type;
        }
      }
      container ospf {
        description
          "OSPF routes Administrative distance";
        leaf intra-area {
          description
            "Intra-area routes";
          type uint32 {
            range "1 .. 255";
          }
        }
        leaf inter-area {
          description
            "Inter-area routes";
          type uint32 {
            range "1 .. 255";
          }
        }
        leaf external {
          description
            "External type 5 and type 7 routes";
          type uint32 {
            range "1 .. 255";
          }
        }
      }
    }
  }

  grouping config-ospf-distribute-list-out-protocols-grouping {
    leaf-list bgp {
      description
        "Border Gateway Protocol (BGP)";
      max-elements "1";
      type ios-types:bgp-as-number-type;
    }
    leaf-list eigrp {
      description
        "Enhanced Interior Gateway Routing Protocol (EIGRP)";
      type uint16 {
        range "1..65535";
      }
    }
    leaf connected {
      description
        "Connected";
      type empty;
    }
    leaf isis {
      description
        "ISO IS-IS";
      type empty;
    }
    container isis-area-tag {
      description
        "ISO IS-IS area-tag";
      leaf-list isis {
        type string;
      }
    }
    leaf lisp {
      description
        "Locator ID Separation Protocol (LISP)";
      type empty;
    }
    leaf nat-route {
      if-feature "ios-features:sdwan";
      description
        "NAT Route";
      type empty;
    }
    leaf-list nhrp {
      description
        "Next Hop Resolution Protocol (NHRP)";
      max-elements "1";
      type uint16 {
        range "1..65535";
      }
    }
    leaf omp {
      if-feature "ios-features:omp";
      description
        "Overlay Management Protocol (OMP)";
      type empty;
    }
    list ospf {
      description
        "Open Shortest Path First (OSPF)";
      key "process-id";
      leaf process-id {
        description
          "Open Shortest Path First (OSPF)";
        type uint16 {
          range "1..65535";
        }
      }
      leaf vrf {
        description
          "VPN Routing/Forwarding Instance";
        type string;
      }
    }
    leaf-list ospfv3 {
      description
        "OSPFv3";
      type uint16 {
        range "1..65535";
      }
    }
    leaf rip {
      description
        "Routing Information Protocol (RIP)";
      type empty;
    }
    leaf static {
      description
        "Static routes";
      type empty;
    }
  }

  grouping config-ospf-distribute-list-grouping {
    container distribute-list {
      description
        "Filter networks in routing updates";
      container access-list {
        list access-list-in {
          key "in";
          leaf ex-access-list {
            description
              "IP expanded access list number";
            type ios-types:exp-acl-type;
          }
          leaf in {
            description
              "Filter service updates";
            must "(not (../../../ios-ospf:prefix-list/ios-ospf:prefix-list-in[ios-ospf:in=current()]))" {
              error-message "distribute-list prefix already exists";
            }
            must "(not (../../../ios-ospf:gateway/ios-ospf:gateway-in[ios-ospf:in=current()]))" {
              error-message "distribute-list gateway already exists";
            }
            must "(not (../../../ios-ospf:route-map/ios-ospf:route-map-in[ios-ospf:in=current()]))" {
              error-message "distribute-list route-map already exists";
            }
            type enumeration {
              enum "in";
            }
          }
        }
        list access-list-out {
          key "out";
          leaf ex-access-list {
            description
              "IP expanded access list number";
            type ios-types:exp-acl-type;
          }
          leaf out {
            description
              "Filter service updates";
            must "(not (../../../ios-ospf:prefix-list/ios-ospf:prefix-list-out[ios-ospf:out=current()]))" {
              error-message "distribute-list prefix already exists";
            }
            type enumeration {
              enum "out";
            }
          }
        }
        list access-list-in-interface {
          key "in interface";
          leaf ex-access-list {
            description
              "IP expanded access list number";
            type ios-types:exp-acl-type;
          }
          leaf in {
            description
              "Filter service updates";
            type enumeration {
              enum "in";
            }
          }
          leaf interface {
            description
              "Interface name";
            type string;
            must "(not (../../../ios-ospf:prefix-list/ios-ospf:prefix-list-in-interface[ios-ospf:interface=current()]))" {
              error-message "distribute-list prefix already exists";
            }
            must "(not (../../../ios-ospf:gateway/ios-ospf:gateway-in-interface[ios-ospf:interface=current()]))" {
              error-message "distribute-list gateway already exists";
            }
          }
        }
        list access-list-out-protocols {
          key "out";
          leaf ex-access-list {
            description
              "IP expanded access list number";
            type ios-types:exp-acl-type;
          }
          leaf out {
            description
              "Filter service updates";
            type enumeration {
              enum "out";
            }
          }
          uses config-ospf-distribute-list-out-protocols-grouping;
        }
      }
      container gateway {
        description
          "Filtering incoming address updates based on gateway";
        list gateway-in {
          key "in";
          leaf gateway {
            description
              "Name of an IP prefix-list";
            type string;
          }
          leaf in {
            description
              "Filter service updates";
            must "(not (../../../ios-ospf:access-list/ios-ospf:access-list-in[ios-ospf:in=current()]))" {
              error-message "distribute-list acess-list already exists";
            }
            must "(not (../../../ios-ospf:prefix-list/ios-ospf:prefix-list-in[ios-ospf:in=current()]))" {
              error-message "distribute-list prefix already exists";
            }
            must "(not (../../../ios-ospf:route-map/ios-ospf:route-map-in[ios-ospf:in=current()]))" {
              error-message "distribute-list route-map already exists";
            }
            type enumeration {
              enum "in";
            }
          }
        }
        list gateway-in-interface {
          key "in interface";
          leaf gateway {
            description
              "Name of an IP prefix-list";
            type string;
          }
          leaf in {
            description
              "Filter service updates";
            type enumeration {
              enum "in";
            }
          }
          leaf interface {
            description
              "Interface name";
            type string;
            must "(not (../../../ios-ospf:access-list/ios-ospf:access-list-in-interface[ios-ospf:interface=current()]))" {
              error-message "distribute-list access-list already exists";
            }
            must "(not (../../../ios-ospf:prefix-list/ios-ospf:prefix-list-in-interface[ios-ospf:interface=current()]))" {
              error-message "distribute-list prefix already exists";
            }
          }
        }
      }
      container prefix-list {
        description
          "Filter prefixes in address updates";
        list prefix-list-in {
          key "in";
          leaf prefix-list {
            description
              "Name of an IP prefix-list";
            type string;
          }
          leaf gateway {
            description
              "Filtering incoming address updates based on gateway";
            type string;
          }
          leaf in {
            description
              "Filter service updates";
            must "(not (../../../ios-ospf:access-list/ios-ospf:access-list-in[ios-ospf:in=current()]))" {
              error-message "distribute-list acess-list already exists";
            }
            must "(not (../../../ios-ospf:gateway/ios-ospf:gateway-in[ios-ospf:in=current()]))" {
              error-message "distribute-list gateway already exists";
            }
            must "(not (../../../ios-ospf:route-map/ios-ospf:route-map-in[ios-ospf:in=current()]))" {
              error-message "distribute-list route-map already exists";
            }
            type enumeration {
              enum "in";
            }
          }
        }
        list prefix-list-out {
          key "out";
          leaf prefix-list {
            description
              "Name of an IP prefix-list";
            type string;
          }
          leaf out {
            description
              "Filter service updates";
            must "(not (../../../ios-ospf:access-list/ios-ospf:access-list-out[ios-ospf:out=current()]))" {
              error-message "distribute-list acess-list already exists";
            }
            type enumeration {
              enum "out";
            }
          }
        }
        list prefix-list-in-interface {
          key "in interface";
          leaf prefix-list {
            description
              "Name of an IP prefix-list";
            type string;
          }
          leaf gateway {
            description
              "Filtering incoming address updates based on gateway";
            type string;
          }
          leaf in {
            description
              "Filter service updates";
            type enumeration {
              enum "in";
            }
          }
          leaf interface {
            description
              "Interface name";
            type string;
            must "(not (../../../ios-ospf:access-list/ios-ospf:access-list-in-interface[ios-ospf:interface=current()]))" {
              error-message "distribute-list access-list already exists";
            }
            must "(not (../../../ios-ospf:gateway/ios-ospf:gateway-in-interface[ios-ospf:interface=current()]))" {
              error-message "distribute-list gateway already exists";
            }
          }
        }
        list prefix-list-out-protocols {
          key "out";
          leaf prefix-list {
            description
              "Name of an IP prefix-list";
            type string;
          }
          leaf out {
            description
              "Filter service updates";
            type enumeration {
              enum "out";
            }
          }
          uses config-ospf-distribute-list-out-protocols-grouping;
        }
      }
      container route-map {
        description
          "Filter prefixes based on the route-map";
        list route-map-in {
          key "in";
          leaf route-map-name {
            description
              "route-map name";
            type string;
          }
          leaf in {
            description
              "Filter service updates";
            must "(not (../../../ios-ospf:access-list/ios-ospf:access-list-in[ios-ospf:in=current()]))" {
              error-message "distribute-list acess-list already exists";
            }
            must "(not (../../../ios-ospf:prefix-list/ios-ospf:prefix-list-in[ios-ospf:in=current()]))" {
              error-message "distribute-list prefix already exists";
            }
            must "(not (../../../ios-ospf:gateway/ios-ospf:gateway-in[ios-ospf:in=current()]))" {
              error-message "distribute-list gateway already exists";
            }
            type enumeration {
              enum "in";
            }
          }
        }
      }
    }
  }

  grouping config-ospf-flex-algo-grouping {
    list flex-algo {
      description
        "Flexible algorithm mode";
      key "number";
      leaf number {
        description
          "Flexible algorithm value";
        type uint32 {
          range "128..255";
        }
      }
      leaf advertise-definition {
        description
          "Advertise definition";
        type boolean;
        default "false";
      }
      leaf metric-type {
        description
          "Metric type";
        type enumeration {
          enum "delay";
          enum "igp-metric";
          enum "te-metric";
        }
        default "igp-metric";
      }
      leaf priority {
        description
          "Priority";
        type uint32 {
          range "0..255";
        }
        default "128";
      }
      container affinity {
        description
          "Assign affinities to flex algo";
        container exclude-any {
          description
            "Affinity attributes to exclude any";
          leaf-list name {
            description
              "Affinity name";
            type string {
              length "1..32";
            }
          }
        }
        container include-all {
          description
            "Affinity attributes to include all";
          leaf-list name {
            description
              "Affinity name";
            type string {
              length "1..32";
            }
          }
        }
        container include-any {
          description
            "Affinity attributes to include any";
          leaf-list name {
            description
              "Affinity name";
            type string {
              length "1..32";
            }
          }
        }
      }
    }
  }

  grouping config-ospf-affinity-map-grouping {
    container affinity-map {
      description
        "Affinity map configuration mode";
      list affinity {
        unique "bit-position";
        key "name";
        leaf name {
          description
            "Affinity name";
          type string {
            length "1..32";
          }
        }
        leaf bit-position {
          description
            "Bit position value";
          type uint32 {
            range "0..255";
          }
          mandatory true;
        }
      }
    }
  }

  grouping config-ospf-fast-reroute-grouping {
    container fast-reroute {
      description
        "LFA FastReroute parameters";
      leaf keep-all-paths {
        description
          "Keep LFA FRR audit trail";
        type empty;
      }
      container per-prefix {
        description
          "Per-prefix LFA FRR parameters";
        container enable {
          description
            "Enable LFA Fast Reroute";
          list area-prefix-priority {
            description
              "Area to enable LFA FRR in";
            key "area";
            leaf area {
              type ios-types:ospf-area-type;
            }
            leaf prefix-priority {
              description
                "Priority of prefixes to be protected";
              type enumeration {
                enum "high";
                enum "low";
              }
            }
          }
          leaf prefix-priority {
            description
              "Priority of prefixes to be protected";
            type enumeration {
              enum "high";
              enum "low";
            }
          }
        }
        container remote-lfa {
          description
            "Remote LFA FastReroute parameters";
          list area {
            key "area-id";
            leaf area-id {
              description
                "Area for remote LFA command";
              type ios-types:ospf-area-type;
            }
            leaf maximum-cost {
              description
                "Maximum distance to tunnel endpoint";
              type uint32 {
                range "1..16777214";
              }
            }
            leaf tunnel {
              description
                "Remote LFA tunnel type";
              type enumeration {
                enum "mpls-ldp";
              }
            }
          }
          leaf maximum-cost {
            description
              "Maximum distance to tunnel endpoint";
            type uint32 {
              range "1..16777214";
            }
          }
          leaf tunnel {
            description
              "Remote LFA tunnel type";
            type enumeration {
              enum "mpls-ldp";
            }
          }
        }
        container tie-break {
          description
            "LFA FRR repair path selection policy tiebreaks";
          container broadcast-interface-disjoint {
            description
              "Interface protection attribute";
            uses config-ospf-fast-reroute-tie-break-index;
          }
          container downstream {
            description
              "Downstream repair path attribute";
            uses config-ospf-fast-reroute-tie-break-index;
          }
          container interface-disjoint {
            description
              "Interface protection attribute";
            uses config-ospf-fast-reroute-tie-break-index;
          }
          container linecard-disjoint {
            description
              "Line card protection attribute";
            uses config-ospf-fast-reroute-tie-break-index;
          }
          container lowest-metric {
            description
              "Lowest metric repair path attribute";
            leaf required {
              status obsolete;
              description
                "Mandatory repair path attribute";
              type empty;
            }
            leaf index {
              description
                "Tiebreak attribute priority";
              type uint8 {
                range "1..255";
              }
            }
          }
          container node-protecting {
            description
              "Node protecting repair path attribute";
            uses config-ospf-fast-reroute-tie-break-index;
          }
          container primary-path {
            description
              "Equal cost multipath attribute";
            uses config-ospf-fast-reroute-tie-break-index;
          }
          container secondary-path {
            description
              "Not-equal cost multipath attribute";
            uses config-ospf-fast-reroute-tie-break-index;
          }
          container srlg {
            description
              "Shared risk link group attribute";
            uses config-ospf-fast-reroute-tie-break-index;
          }
        }
      }
    }
  }

  grouping config-ospf-fast-reroute-tie-break-index {
    leaf required {
      description
        "Mandatory repair path attribute";
      type empty;
    }
    leaf index {
      description
        "Tiebreak attribute priority";
      type uint8 {
        range "1..255";
      }
    }
  }

  grouping config-ospf-ignore-grouping {
    container ignore {
      description
        "Do not complain about specific event";
      container lsa {
        description
          "Do not complain upon receiving LSA of the specified type";
        leaf mospf {
          description
            "MOSPF Type 6 LSA";
          type boolean;
          default "false";
        }
      }
    }
  }

  grouping config-ospf-interface-id-grouping {
    container interface-id {
      description
        "Source of the interface ID";
      leaf snmp-if-index {
        description
          "SNMP MIB ifIndex";
        type boolean;
        default "false";
      }
    }
  }

  grouping config-ospf-limit-grouping {
    container limit {
      description
        "Limit a specific OSPF feature";
      container retransmissions {
        description
          "LS update, DBD, and LS request retransmissions";
        leaf dc {
          description
            "Demand circuit retransmissions";
          type ios-types:limit-dc-non-dc-type;
          default "24";
        }
        leaf non-dc {
          description
            "Non-demand-circuit retransmissions";
          type ios-types:limit-dc-non-dc-type;
          default "24";
        }
      }
    }
  }

  grouping config-ospf-local-rib-criteria-grouping {
    container local-rib-criteria {
      description
        "Enable or disable usage of local RIB as route criteria";
      presence "true";
      leaf forwarding-address {
        description
          "Local RIB used to validate external/NSSA forwarding addresses";
        type empty;
      }
      leaf inter-area-summary {
        description
          "Local RIB used as criteria for inter-area summaries";
        type empty;
      }
      leaf nssa-translation {
        description
          "Local RIB used as criteria for NSSA translation";
        type empty;
      }
    }
  }

  grouping config-ospf-log-adjacency-changes-grouping {
    choice log-adjacency-changes-choice {
      default "log-adjacency-changes";
      leaf log-adjacency-changes {
        description
          "Log changes in adjacency state";
        type boolean;
        default "true";
      }
      container log-adjacency-changes-detail {
        container log-adjacency-changes {
          leaf detail {
            description
              "Log all state changes";
            type empty;
          }
        }
      }
    }
  }

  grouping config-ospf-max-lsa-grouping {
    container max-lsa {
      description
        "maximum number of LSAs OSPF process will receive";
      leaf number {
        description
          "Maximum number of non self-generated LSAs this process can receive";
        type uint32 {
          range "1 .. 4294967294";
        }
      }
      leaf threshold-value {
        description
          "Threshold value (%) at which to generate a warning msg";
        type uint32 {
          range "1 .. 100";
        }
        default "75";
      }
      choice max-lsa-choice {
        default "max-lsa-options";
        container max-lsa-options {
          description
            "max-lsa options";
          leaf ignore-time {
            description
              "time during which all adjacencies are suppressed";
            type uint32 {
              range "1 .. 17895";
            }
            default "5";
          }
          leaf reset-time {
            description
              "time after which ignore-count is reset to zero";
            type uint32 {
              range "2 .. 35791";
            }
            default "10";
          }
          leaf ignore-count {
            description
              "maximum number of times adjacencies can be suppressed";
            type uint32 {
              range "1 .. 65534";
            }
            default "5";
          }
        }
        leaf warning-only {
          description
            "Only give warning message when limit is exceeded";
          type empty;
        }
      }
    }
  }

  grouping config-ospf-max-metric-grouping {
    container max-metric {
      description
        "Set maximum metric";
      container router-lsa {
        description
          "Maximum metric in self-originated router-LSAs";
        presence "true";
        leaf include-stub {
          description
            "Set maximum metric for stub links in router-LSAs";
          type empty;
        }
        container summary-lsa {
          description
            "Override summary-lsa metric with max-metric value";
          presence "true";
          leaf metric {
            type uint32 {
              range "1 .. 16777214";
            }
            default "16711680";
          }
        }
        container external-lsa {
          description
            "Override external-lsa metric with max-metric value";
          presence "true";
          leaf metric {
            type uint32 {
              range "1 .. 16777214";
            }
            default "16711680";
          }
        }
        container on-startup {
          description
            "Set maximum metric temporarily after reboot";
          choice time-wait-for-bgp-choice {
            leaf time {
              type uint32 {
                range "5 .. 86400";
              }
            }
            leaf wait-for-bgp {
              description
                "Let BGP decide when to originate router-LSA with normal metric";
              type empty;
            }
          }
        }
      }
    }
  }

  grouping config-ospf-maximum-paths-grouping {
    leaf maximum-paths {
      description
        "Forward packets over multiple paths";
      type uint32 {
        range "1 .. 32";
      }
      default "4";
    }
  }

  grouping config-ospf-microloop-grouping {
    container microloop {
      description
        "Traffic microloop control parameters";
      container avoidance {
        description
          "Traffic microloop avoidance parameters";
        choice prefix-choice {
          leaf all {
            type empty;
          }
          leaf disable {
            description
              "Microloop avoidance auto-enable prohibited";
            type empty;
          }
          leaf protected {
            description
              "Microloop avoidance for protected prefixes only";
            type empty;
          }
        }
        leaf rib-update-delay {
          description
            "Delay before updating the RIB";
          type uint32 {
            range "1..600000";
          }
          default "5000";
        }
      }
    }
  }

  grouping config-ospf-mpls-grouping {
    container mpls {
      description
        "Configure MPLS routing protocol parameters";
      container ldp {
        description
          "routing protocol commands for MPLS LDP";
        container autoconfig {
          description
            "Configure LDP automatic configuration";
          presence "true";
          leaf-list area {
            description
              "Configure an OSPF area to run MPLS LDP";
            type ios-types:ospf-area-type;
          }
        }
        container sync {
          description
            "Configure LDP-IGP Synchronization";
          presence "true";
        }
      }
      container traffic-eng {
        description
          "routing protocol commands for MPLS Traffic Engineering";
        leaf multicast-intact {
          description
            "MPLS TE and PIM interaction";
          type empty;
        }
        leaf-list area {
          description
            "configure an ospf area to run MPLS Traffic Engineering";
          type ios-types:ospf-area-type;
        }
        container autoroute-exclude {
          description
            "MPLS TE autoroute exclude";
          leaf prefix-list {
            description
              "Filter prefixes";
            type string;
          }
        }
        list interface {
          description
            "MPLS TE interface configuration for this OSPF process";
          key "name-id";
          leaf name-id {
            description
              "Interface name and ID";
            type string;
          }
          leaf area {
            description
              "Advertise MPLS TE information for this interface into area";
            type enumeration {
              enum "0";
            }
          }
        }
        list mesh-group {
          description
            "Traffic Engineering Mesh-Group advertisement";
          key "id area";
          leaf id {
            description
              "Mesh Group ID: <0..4294967295>";
            type uint32 {
              range "0..4294967295";
            }
          }
          leaf area {
            description
              "configure flooding scope as area";
            type ios-types:ospf-area-type;
          }
          leaf interface {
            description
              "Interface name and ID";
            type string;
          }
        }
        leaf router-id {
          description
            "Traffic Engineering stable IP address for system";
          type string;
        }
      }
    }
  }

  grouping config-ospf-multicast-intact-grouping {
    leaf multicast-intact {
      description
        "Install IGP paths in multicast RIB when tunnel path is installed in unicast RIB";
      type boolean;
      default "false";
    }
  }

  grouping config-ospf-neighbor-grouping {
    list neighbor {
      description
        "Specify a neighbor router";
      key "ip";
      leaf ip {
        description
          "Neighbor address";
        type inet:ipv4-address;
      }
      leaf priority {
        description
          "OSPF priority of non-broadcast neighbor";
        type uint32 {
          range "0 .. 255";
        }
      }
      leaf poll-interval {
        description
          "OSPF dead-router polling interval of non-broadcast neighbor";
        type uint32 {
          range "0 .. 65535";
        }
      }
      leaf cost {
        description
          "OSPF cost for point-to-multipoint neighbor";
        type uint32 {
          range "1 .. 65535";
        }
      }
      container database-filter {
        description
          "Filter OSPF LSA during synchronization and flooding for point-to-multipoint neighbor";
        container all {
          description
            "Filter all LSA";
          leaf out {
            description
              "Outgoing LSA";
            type boolean;
            default "false";
          }
        }
      }
    }
  }

  grouping config-ospf-network-grouping {
    list network {
      description
        "Enable routing on an IP network";
      key "ip wildcard";
      leaf ip {
        description
          "Network number";
        type inet:ipv4-address;
      }
      leaf wildcard {
        description
          "OSPF wild card bits";
        type inet:ipv4-address;
      }
      leaf area {
        description
          "Set the OSPF area ID";
        type ios-types:ospf-area-type;
      }
    }
  }

  grouping config-ospf-nsf-grouping {
    container nsf {
      description
        "Non-stop forwarding";
      choice nsf-cisco-ietf {
        container nsf-cisco {
          description
            "Cisco Non-stop forwarding";
          presence "true";
          container enforce {
            description
              "Cancel NSF restart when non-NSF-aware neighbors detected";
            leaf global {
              description
                "For the whole OSPF process";
              type empty;
            }
          }
        }
        container nsf-ietf {
          description
            "IETF graceful restart";
          presence "true";
          leaf restart-interval {
            description
              "Graceful restart interval";
            type uint16 {
              range "1..1800";
            }
            default "120";
            units "seconds";
          }
        }
      }
      choice cisco-ietf {
        status obsolete;
        description
          "cisco-ietf (DEPRECATED, use nsf-cisco-ietf)";
        container cisco {
          status obsolete;
          description
            "Cisco Non-stop forwarding (DEPRECATED, use nsf-cisco)";
          presence "true";
          container enforce {
            status obsolete;
            description
              "Cancel NSF restart when non-NSF-aware neighbors detected";
            leaf global {
              status obsolete;
              description
                "For the whole OSPF process";
              type empty;
            }
          }
        }
        container ietf {
          description
            "IETF graceful restart";
          status obsolete;
          leaf restart-interval {
            description
              "Graceful restart interval (DEPRECATED, use nsf-ietf)";
            status obsolete;
            type uint16 {
              range "1..1800";
            }
            default "120";
            units "seconds";
          }
        }
      }
      choice cisco-helper-choice {
        default "cisco-helper";
        container cisco-helper {
          description
            "Cisco Non-stop forwarding";
          container cisco {
            description
              "Cisco Non-stop forwarding";
            leaf helper {
              description
                "helper support";
              type boolean;
              default "true";
            }
          }
        }
        container cisco-helper-disable {
          description
            "IETF graceful restart";
          container cisco {
            description
              "IETF graceful restart";
            container helper {
              description
                "helper support";
              leaf disable {
                description
                  "disable helper support";
                type empty;
              }
            }
          }
        }
      }
      choice ietf-helper-choice {
        default "ietf-helper";
        container ietf-helper {
          description
            "IETF graceful restart";
          container ietf {
            description
              "IETF graceful restart";
            leaf helper {
              description
                "helper support";
              type boolean;
              default "true";
            }
          }
        }
        container ietf-helper-disable {
          description
            "IETF graceful restart";
          container ietf {
            description
              "IETF graceful restart";
            container helper {
              description
                "helper support";
              leaf disable {
                description
                  "disable helper support";
                type empty;
              }
            }
          }
        }
      }
      container ietf-helper-strict-lsa-checking {
        description
          "IETF graceful restart";
        container ietf {
          description
            "IETF graceful restart";
          container helper {
            description
              "helper support";
            leaf strict-lsa-checking {
              description
                "enable helper strict LSA checking";
              type empty;
            }
          }
        }
      }
    }
  }

  grouping config-ospf-nsr-grouping {
    leaf nsr {
      description
        "Enable non-stop routing";
      type boolean;
      default "false";
    }
  }

  grouping config-ospf-passive-interface-grouping {
    container passive-interface {
      description
        "Suppress routing updates on an interface";
      choice passive-interface-choice {
        default "default";
        leaf default {
          description
            "Suppress routing updates on all interfaces";
          type boolean;
          default "false";
        }
        leaf-list interface {
          type string;
        }
      }
    }
  }

  grouping config-ospf-prefix-priority-grouping {
    container prefix-priority {
      description
        "OSPF prefix priority";
      container high {
        description
          "High prefix priority";
        leaf route-map {
          description
            "Prefix priority selection by route-map";
          type string;
        }
      }
    }
  }

  grouping config-ospf-prefix-suppression-grouping {
    leaf prefix-suppression {
      description
        "OSPF prefix suppression";
      type boolean;
      default "false";
    }
  }

  grouping config-ospf-priority-grouping {
    leaf priority {
      description
        "OSPF topology priority";
      type uint8 {
        range "0..127";
      }
      default "64";
    }
  }

  grouping config-ospf-process-min-time-grouping {
    container process-min-time {
      description
        "Percentage of quantum to be used before releasing CPU";
      leaf percent {
        description
          "percent";
        type uint32 {
          range "1 .. 100";
        }
      }
    }
  }

  grouping config-ospf-queue-depth-grouping {
    container queue-depth {
      description
        "OSPF Hello/Router process queue depth";
      container hello {
        description
          "OSPF Hello process queue depth";
        leaf options {
          type union {
            type uint32 {
              range "1 .. 2147483647";
            }
            type enumeration {
              enum "unlimited";
            }
          }
          default "unlimited";
        }
      }
      container update {
        description
          "OSPF Router process queue depth";
        leaf options {
          type union {
            type uint32 {
              range "1 .. 2147483647";
            }
            type enumeration {
              enum "unlimited";
            }
          }
          default "200";
        }
      }
    }
  }

  grouping config-ospf-redist-common-grouping {
    leaf metric {
      description
        "Metric for redistributed routes";
      type uint32 {
        range "0..16777214";
      }
    }
    leaf metric-type {
      description
        "OSPF/IS-IS exterior metric type for redistributed routes";
      type ios-types:redist-ospf-external-type;
    }
    leaf nssa-only {
      description
        "Limit redistributed routes to NSSA areas";
      type empty;
    }
    leaf subnets {
      description
        "Consider subnets for redistribution into OSPF";
      type empty;
    }
    leaf route-map {
      description
        "Route map reference";
      type string;
    }
    leaf tag {
      description
        "Set tag for routes redistributed into OSPF";
      type uint32 {
        range "0..4294967295";
      }
    }
  }

  grouping config-ospf-redist-common-for-list-grouping {
    leaf metric {
      description
        "Metric for redistributed routes";
      type uint32 {
        range "0..16777214";
      }
    }
    leaf metric-type {
      description
        "OSPF/IS-IS exterior metric type for redistributed routes";
      type ios-types:redist-ospf-external-type;
    }
    leaf nssa-only {
      description
        "Limit redistributed routes to NSSA areas";
      type empty;
    }
    leaf subnets {
      description
        "Consider subnets for redistribution into OSPF";
      type empty;
    }
    leaf route-map {
      description
        "Route map reference";
      type string;
    }
    leaf tag {
      description
        "Set tag for routes redistributed into OSPF";
      type uint32 {
        range "0..4294967295";
      }
    }
  }

  grouping config-ospf-redist-common-with-delete-grouping {
    leaf metric {
      description
        "Metric for redistributed routes";
      type uint32 {
        range "0..16777214";
      }
    }
    leaf metric-type {
      description
        "OSPF/IS-IS exterior metric type for redistributed routes";
      type ios-types:redist-ospf-external-type;
    }
    leaf nssa-only {
      description
        "Limit redistributed routes to NSSA areas";
      type empty;
    }
    leaf subnets {
      description
        "Consider subnets for redistribution into OSPF";
      type empty;
    }
    leaf route-map {
      description
        "Route map reference";
      type string;
    }
    leaf tag {
      description
        "Set tag for routes redistributed into OSPF";
      type uint32 {
        range "0..4294967295";
      }
    }
  }

  grouping config-ospf-redist-application-grouping {
    list application {
      description
        "Application";
      key "application-name";
      max-elements "1";
      leaf application-name {
        description
          "Application name";
        type string;
      }
      uses config-ospf-redist-common-for-list-grouping;
    }
  }

  grouping config-ospf-redist-bgp-grouping {
    list bgp {
      description
        "Border Gateway Protocol (BGP)";
      key "as";
      max-elements "1";
      leaf as {
        description
          "Autonomous system number";
        type ios-types:bgp-as-number-type;
      }
      uses config-ospf-redist-common-for-list-grouping;
    }
  }

  grouping config-ospf-redist-eigrp-grouping {
    list eigrp {
      description
        "Enhanced Interior Gateway Routing Protocol (EIGRP)";
      key "as";
      leaf as {
        description
          "Autonomous system number";
        type uint16 {
          range "1..65535";
        }
      }
      uses config-ospf-redist-common-with-delete-grouping;
    }
  }

  grouping config-ospf-redist-connected-grouping {
    container connected {
      description
        "Connected";
      presence "true";
      uses config-ospf-redist-common-grouping;
    }
  }

  grouping config-ospf-redist-isis-grouping {
    container isis {
      description
        "ISO IS-IS";
      presence "true";
      must "/ios:native/ios:router/ios-isis:isis" {
        error-message "Router isis must be configured before redistribute isis and deleted after redistribute isis";
      }
      uses config-ospf-redist-isis-levels-grouping;
      uses config-ospf-redist-common-with-delete-grouping;
    }
    container isis-area-tag {
      description
        "ISO IS-IS area-tag";
      list isis {
        description
          "ISO IS-IS";
        key "area-tag";
        leaf area-tag {
          description
            "ISO IS-IS area-tag";
          type leafref {
            path "/ios:native/ios:router/ios-isis:isis-container/ios-isis:isis/ios-isis:area-tag";
          }
        }
        uses config-ospf-redist-isis-levels-grouping;
        uses config-ospf-redist-common-with-delete-grouping;
      }
    }
  }

  grouping config-ospf-redist-isis-levels-grouping {
    leaf routes {
      type enumeration {
        enum "level-1";
        enum "level-2";
        enum "level-1-2";
      }
      default "level-2";
    }
  }

  grouping config-ospf-redist-lisp-grouping {
    container lisp {
      description
        "Locator ID Separation Protocol (LISP)";
      presence "true";
      uses config-ospf-redist-common-grouping;
    }
  }

  grouping config-ospf-redist-maximum-prefix-grouping {
    container maximum-prefix {
      description
        "Maximum number of prefixes redistributed to protocol";
      leaf maximum-prefix-count {
        description
          "Maximum number of IP prefixes redistributed";
        type uint32 {
          range "1..4294967295";
        }
      }
      leaf threshold {
        description
          "Threshold value (%) at which to generate a warning message";
        type uint8 {
          range "1..100";
        }
      }
      leaf warning-only {
        description
          "Only give warning message when limit is exceeded";
        type empty;
      }
    }
  }

  grouping config-ospf-redist-mobile-grouping {
    container mobile {
      description
        "Mobile routes";
      presence "true";
      uses config-ospf-redist-common-grouping;
    }
  }

  grouping config-ospf-redist-nat-route-grouping {
    container nat-route {
      if-feature "ios-features:sdwan";
      description
        "NAT Route";
      presence "true";
      leaf dia {
        description
          "Redistribute NAT Direct Internet Access routes";
        type empty;
      }
      leaf outside {
        description
          "Redistribute NAT Outside routes";
        type empty;
      }
      uses config-ospf-redist-common-grouping;
    }
  }

  grouping config-ospf-redist-nhrp-grouping {
    list nhrp {
      description
        "Next Hop Resolution Protocol (NHRP)";
      key "process-id";
      leaf process-id {
        description
          "Process ID";
        type uint16 {
          range "1..65535";
        }
      }
      uses config-ospf-redist-common-for-list-grouping;
    }
  }

  grouping config-ospf-redist-omp-grouping {
    container omp {
      if-feature "ios-features:omp";
      description
        "Overlay Management Protocol (OMP)";
      presence "true";
      uses config-ospf-redist-common-grouping;
    }
  }

  grouping config-ospf-redist-odr-grouping {
    container odr {
      description
        "On Demand stub Routes";
      presence "true";
      uses config-ospf-redist-common-grouping;
    }
  }

  grouping config-ospf-redist-ospf-match-grouping {
    container match {
      description
        "Redistribution of OSPF routes";
      leaf internal {
        description
          "Redistribute OSPF internal routes";
        type empty;
      }
      leaf external-1 {
        description
          "Redistribute OSPF external routes";
        type ios-types:redist-ospf-external-type;
      }
      leaf external-2 {
        description
          "Redistribute OSPF external routes";
        type ios-types:redist-ospf-external-type;
      }
      leaf nssa-external-1 {
        description
          "Redistribute OSPF NSSA external routes";
        type ios-types:redist-ospf-external-type;
      }
      leaf nssa-external-2 {
        description
          "Redistribute OSPF NSSA external routes";
        type ios-types:redist-ospf-external-type;
      }
    }
  }

  grouping config-ospf-redist-ospf-grouping {
    list ospf {
      description
        "Open Shortest Path First (OSPF)";
      key "process-id";
      leaf process-id {
        description
          "Process ID";
        type uint16 {
          range "1..65535";
        }
      }
      uses config-ospf-redist-ospf-match-grouping;
      uses config-ospf-redist-common-for-list-grouping;
    }
  }

  grouping config-ospf-redist-ospf-vrf-grouping {
    list ospf {
      description
        "Open Shortest Path First (OSPF)";
      key "process-id";
      leaf process-id {
        description
          "Process ID";
        type uint16 {
          range "1..65535";
        }
      }
      leaf vrf {
        description
          "VPN Routing/Forwarding Instance";
        type string;
      }
      uses config-ospf-redist-ospf-match-grouping;
      uses config-ospf-redist-common-for-list-grouping;
    }
  }

  grouping config-ospf-redist-ospfv3-grouping {
    list ospfv3 {
      description
        "OSPFv3";
      key "process-id";
      leaf process-id {
        description
          "Process ID";
        type uint16 {
          range "1..65535";
        }
      }
      uses config-ospf-redist-ospf-match-grouping;
      uses config-ospf-redist-common-for-list-grouping;
    }
  }

  grouping config-ospf-redist-rip-grouping {
    container rip {
      description
        "Routing Information Protocol (RIP)";
      presence "true";
      uses config-ospf-redist-common-grouping;
    }
  }

  grouping config-ospf-redist-static-grouping {
    container static {
      description
        "Static routes";
      presence "true";
      uses config-ospf-redist-common-grouping;
    }
  }

  grouping config-ospf-redist-vrf-grouping {
    list vrf {
      description
        "Specify a source VRF";
      key "vrf-name";
      leaf vrf-name {
        description
          "Source VRF name";
        type union {
          type string;
          type enumeration {
            enum "global";
          }
        }
      }
      uses config-ospf-redist-application-grouping;
      uses config-ospf-redist-bgp-grouping;
      uses config-ospf-redist-eigrp-grouping;
      uses config-ospf-redist-connected-grouping;
      uses config-ospf-redist-isis-grouping;
      uses config-ospf-redist-lisp-grouping;
      uses config-ospf-redist-mobile-grouping;
      uses config-ospf-redist-nat-route-grouping;
      uses config-ospf-redist-nhrp-grouping;
      uses config-ospf-redist-omp-grouping;
      uses config-ospf-redist-odr-grouping;
      uses config-ospf-redist-ospf-grouping;
      uses config-ospf-redist-ospfv3-grouping;
      uses config-ospf-redist-rip-grouping;
      uses config-ospf-redist-static-grouping;
    }
  }

  grouping config-ospf-redistribute-grouping {
    container redistribute {
      description
        "Redistribute information from another routing protocol";
      uses config-ospf-redist-application-grouping;
      uses config-ospf-redist-bgp-grouping;
      uses config-ospf-redist-eigrp-grouping;
      uses config-ospf-redist-connected-grouping;
      uses config-ospf-redist-isis-grouping;
      uses config-ospf-redist-lisp-grouping;
      uses config-ospf-redist-maximum-prefix-grouping;
      uses config-ospf-redist-mobile-grouping;
      uses config-ospf-redist-nat-route-grouping;
      uses config-ospf-redist-nhrp-grouping;
      uses config-ospf-redist-omp-grouping;
      uses config-ospf-redist-odr-grouping;
      uses config-ospf-redist-ospf-vrf-grouping;
      uses config-ospf-redist-ospfv3-grouping;
      uses config-ospf-redist-rip-grouping;
      uses config-ospf-redist-static-grouping;
      uses config-ospf-redist-vrf-grouping;
    }
  }

  grouping config-ospf-router-id-grouping {
    leaf router-id {
      description
        "Override configured router identifier (peers will reset)";
      type inet:ipv4-address;
    }
  }

  grouping config-ospf-shutdown-grouping {
    leaf shutdown {
      description
        "Shutdown the OSPF protocol under the current instance";
      type boolean;
      default "false";
    }
  }

  grouping config-ospf-snmp-grouping {
    container snmp {
      description
        "Modify snmp parameters";
      list context {
        description
          "Configure a SNMP context";
        key "name";
        leaf name {
          description
            "Context Name";
          type string;
        }
        container community {
          description
            "Configure a SNMP v2c Community string and access privs";
          leaf community-string {
            description
              "SNMP community string";
            type string;
          }
          leaf ro-rw {
            type enumeration {
              enum "RO";
              enum "RW";
            }
            default "RO";
          }
          leaf access-list {
            description
              "IP expanded access list number";
            type ios-types:exp-acl-type;
          }
          leaf ipv6 {
            description
              "Specify IPv6 Named Access-List";
            type string;
          }
        }
      }
    }
  }

  grouping config-ospf-summary-address-grouping {
    list summary-address {
      description
        "Configure IP address summaries";
      key "ip mask";
      leaf ip {
        description
          "IP summary address";
        type inet:ipv4-address;
      }
      leaf mask {
        description
          "Summary mask";
        type inet:ipv4-address;
      }
      choice nssa-only-no-advertise-choice {
        container nssa-only-tag {
          leaf nssa-only {
            description
              "Limit summary to NSSA areas";
            type empty;
          }
          leaf tag {
            description
              "Set tag";
            type uint32 {
              range "0 .. 4294967295";
            }
          }
        }
        leaf not-advertise {
          description
            "Do not advertise when translating OSPF type-7 LSA";
          type empty;
        }
      }
    }
  }

  grouping config-ospf-table-map-grouping {
    container table-map {
      description
        "Map external entry attributes into routing table";
      leaf name {
        description
          "route-map name";
        type string;
      }
      leaf filter {
        description
          "Selective route download";
        type empty;
      }
    }
  }

  grouping config-ospf-timers-grouping {
    container timers {
      description
        "Adjust routing timers";
      container lsa {
        description
          "OSPF LSA timers";
        leaf arrival {
          description
            "OSPF LSA arrival timer";
          type uint32 {
            range "0 .. 600000";
          }
          default "100";
        }
      }
      container pacing {
        description
          "OSPF pacing timers";
        leaf flood {
          description
            "OSPF flood pacing timer";
          type uint32 {
            range "5 .. 100";
          }
          default "33";
        }
        leaf lsa-group {
          description
            "OSPF LSA group pacing timer";
          type uint32 {
            range "10 .. 1800";
          }
          default "240";
        }
        leaf retransmission {
          description
            "OSPF retransmission pacing timer";
          type uint32 {
            range "5 .. 200";
          }
          default "66";
        }
      }
      container throttle {
        description
          "OSPF throttle timers";
        container lsa {
          description
            "OSPF LSA throttle timers";
          leaf delay {
            description
              "Delay to generate first occurrence of LSA in milliseconds";
            type uint32 {
              range "0 .. 600000";
            }
            default "50";
          }
          leaf min-delay {
            description
              "Minimum delay between originating the same LSA in milliseconds";
            must "../delay <= ." {
              error-message "minimum delay has to greater then or equal to delay";
            }
            type uint32 {
              range "1 .. 600000";
            }
            default "200";
          }
          leaf max-delay {
            description
              "Maximum delay between originating the same LSA in milliseconds";
            must "../min-delay <= ." {
              error-message "maximum delay has to greater then or equal to minimum delay";
            }
            type uint32 {
              range "1 .. 600000";
            }
            default "5000";
          }
        }
        container spf {
          description
            "OSPF SPF throttle timers";
          leaf delay {
            description
              "Delay between receiving a change to SPF calculation in milliseconds";
            type uint32 {
              range "1 .. 600000";
            }
            default "50";
          }
          leaf min-delay {
            description
              "Delay between first and second SPF calculation in milliseconds";
            must "../delay <= ." {
              error-message "minimum delay has to greater then or equal to delay";
            }
            type uint32 {
              range "1 .. 600000";
            }
            default "200";
          }
          leaf max-delay {
            description
              "Maximum wait time in milliseconds for SPF calculations";
            must "../min-delay <= ." {
              error-message "maximum delay has to greater then or equal to minimum delay";
            }
            type uint32 {
              range "1 .. 600000";
            }
            default "5000";
          }
        }
      }
    }
  }

  grouping config-ospf-traffic-share-grouping {
    container traffic-share {
      description
        "How to compute traffic share over alternate paths";
      leaf min {
        description
          "All traffic shared among min metric paths";
        type enumeration {
          enum "across-interfaces";
        }
      }
    }
  }

  grouping config-ospf-ttl-security-grouping {
    container ttl-security {
      description
        "TTL security check";
      container all-interfaces {
        description
          "Enable TTL Security on all interfaces";
        presence "true";
        leaf hops {
          description
            "IP hops";
          type uint8 {
            range "1..254";
          }
        }
      }
    }
  }

  grouping config-ospf-interface-adjacency-grouping {
    container adjacency {
      description
        "Adjacency staggering";
      choice stagger-choice {
        default "stagger";
        leaf stagger {
          description
            "Adjacency staggering";
          type boolean;
          default "false";
        }
        container stagger-disable {
          description
            "OSPF Adjacency Stagger disable";
          container stagger {
            description
              "Adjacency staggering";
            leaf disable {
              description
                "Disable adjacency staggering on this interface";
              type empty;
            }
          }
        }
      }
    }
  }

  grouping config-ospf-interface-authentication-grouping {
    container authentication {
      description
        "Enable authentication";
      choice auth-type-choice {
        leaf key-chain {
          description
            "Use a key-chain for cryptographic authentication keys";
          type string;
        }
        leaf message-digest {
          description
            "Use message-digest authentication";
          type empty;
        }
        leaf null {
          description
            "Use no authentication";
          type empty;
        }
        leaf clear-text {
          description
            "Use Clear Text authentication";
          type empty;
        }
      }
    }
  }

  grouping config-ospf-interface-authentication-key-grouping {
    container authentication-key {
      description
        "Authentication password (key)";
      leaf auth-type {
        description
          "Encryption type (0 for not yet encrypted, 7 for proprietary)";
        type uint8 {
          range "0 .. 7";
        }
      }
      leaf auth-key {
        description
          "The OSPF password (key) (maximum 8 characters)";
        type string {
          length "1..8";
        }
      }
    }
  }

  grouping config-ospf-interface-bfd-grouping {
    container bfd {
      description
        "BFD on this interface";
      presence "true";
      choice bfd-choice {
        leaf disable {
          description
            "Disable BFD on this interface";
          type empty;
        }
        leaf strict-mode {
          description
            "Enable BFD in strict mode";
          type empty;
        }
      }
    }
  }

  grouping config-ospf-interface-cost-grouping {
    leaf cost {
      description
        "Route cost of this interface";
      type uint16 {
        range "1..65535";
      }
    }
  }

  grouping config-ospf-interface-database-filter-grouping {
    container database-filter {
      description
        "Filter OSPF LSA during synchronization and flooding";
      container all {
        description
          "Filter all LSA";
        leaf out {
          description
            "Outgoing LSA";
          type boolean;
          default "false";
        }
      }
    }
  }

  grouping config-ospf-interface-demand-circuit-grouping {
    choice demand-circuit-choice {
      default "demand-circuit";
      leaf demand-circuit {
        description
          "OSPF Demand Circuit";
        type boolean;
        default "false";
      }
      container demand-circuit-ignore {
        description
          "OSPF Demand Circuit Ignore";
        container demand-circuit {
          description
            "OSPF Demand Circuit";
          leaf ignore {
            description
              "Ignore demand circuit auto-negotiation requests";
            type empty;
          }
        }
      }
    }
  }

  grouping config-ospf-interface-dead-interval-grouping {
    leaf dead-interval {
      description
        "Interval after which a neighbor is declared dead";
      type uint16 {
        range "1..65535";
      }
      default "40";
      units "seconds";
    }
  }

  grouping config-ospf-interface-fast-reroute-grouping {
    container fast-reroute {
      description
        "LFA FastReroute parameters";
      container per-prefix {
        description
          "Per-prefix LFA FRR parameters";
        container candidate {
          description
            "If interface can be protecting";
          presence "true";
          leaf disable {
            description
              "Disable LFA FRR interface protection";
            type empty;
          }
        }
        container protection {
          description
            "If interface can be protected";
          presence "true";
          leaf disable {
            description
              "Disable LFA FRR interface protection";
            type empty;
          }
        }
      }
    }
  }

  grouping config-ospf-interface-flood-reduction-grouping {
    leaf flood-reduction {
      description
        "OSPF Flood Reduction";
      type boolean;
      default "false";
    }
  }

  grouping config-ospf-interface-hello-interval-grouping {
    leaf hello-interval {
      description
        "Time between HELLO packets";
      type uint32 {
        range "1..65535";
      }
      default "10";
    }
  }

  grouping config-ospf-interface-lls-ip-grouping {
    container lls {
      description
        "Link-local Signaling (LLS) support";
      presence "true";
      leaf disable {
        description
          "disable LLS";
        type empty;
      }
    }
  }

  grouping config-ospf-interface-message-digest-key-grouping {
    list message-digest-key {
      description
        "Message digest authentication password (key)";
      key "id";
      leaf id {
        description
          "Key ID";
        type uint8 {
          range "1 .. 255";
        }
      }
      container md5 {
        description
          "Use MD5 algorithm";
        leaf auth-type {
          description
            "Encryption type (0 for not yet encrypted, 7 for proprietary)";
          type uint8 {
            range "0 .. 7";
          }
        }
        leaf auth-key {
          description
            "The OSPF password (key) (only the first 16 characters are used)";
          type string {
            pattern ".*";
          }
        }
      }
    }
  }

  grouping config-ospf-interface-multi-area-grouping {
    container multi-area {
      list multi-area-id {
        description
          "Set the OSPF multi-area ID";
        key "area-id";
        leaf area-id {
          description
            "OSPF multi-area ID";
          type ios-types:ospf-area-type;
        }
      }
      list multi-area-id-cost {
        description
          "Set the OSPF multi-area ID";
        key "area-id";
        leaf area-id {
          description
            "OSPF multi-area ID";
          type ios-types:ospf-area-type;
        }
        leaf cost {
          description
            "Interface cost";
          type uint32 {
            range "1..65535";
          }
        }
      }
      list multi-area-id-delay {
        description
          "Set the OSPF multi-area ID";
        key "area-id";
        leaf area-id {
          description
            "OSPF multi-area ID";
          type ios-types:ospf-area-type;
        }
        uses config-ospf-interface-delay-normalize-grouping;
      }
    }
  }

  grouping config-ospf-interface-delay-normalize-grouping {
    container delay {
      description
        "Set OSPF delay parameters";
      container normalize {
        description
          "Set OSPF delay normalization parameters";
        leaf interval {
          description
            "Set OSPF delay normalization interval";
          type uint32 {
            range "1..16777215";
          }
        }
        leaf offset {
          description
            "Set OSPF delay normalization offset";
          type uint32 {
            range "0..16777215";
          }
        }
      }
    }
  }

  grouping config-ospf-interface-mtu-ignore-grouping {
    leaf mtu-ignore {
      description
        "Ignores the MTU in DBD packets";
      type boolean;
      default "false";
    }
  }

  grouping config-ospf-interface-network-ip-grouping {
    container network {
      description
        "Network type";
      choice network-type-choice {
        leaf broadcast {
          description
            "Specify OSPF broadcast multi-access network";
          type empty;
        }
        leaf non-broadcast {
          description
            "Specify OSPF NBMA network";
          type empty;
        }
        container point-to-multipoint {
          description
            "Specify OSPF point-to-multipoint network";
          presence "true";
          leaf non-broadcast {
            description
              "Specify non-broadcast point-to-mpoint network";
            type empty;
          }
        }
        leaf point-to-point {
          description
            "Specify OSPF point-to-point network";
          type empty;
        }
      }
    }
  }

  grouping config-ospf-interface-prefix-suppression-grouping {
    container prefix-suppression {
      description
        "OSPF prefix suppression";
      presence "true";
      leaf disable {
        description
          "Disable prefix suppression";
        type empty;
      }
    }
  }

  grouping config-ospf-interface-priority-common-grouping {
    leaf priority {
      description
        "Router priority";
      type uint8 {
        range "0..255";
      }
      default "1";
    }
  }

  grouping config-ospf-interface-process-id-igrouping {
    list process-id {
      must "not (../../../../ios:switchport-conf/ios:switchport) or (../../../../ios:switchport-conf/ios:switchport = 'false')" {
        error-message "To configure ip ospf, set switchport to false 1st; To change switchport from false to true, delete ip ospf 1st ";
      }
      key "id";
      leaf id {
        description
          "Process ID";
        type uint16 {
          range "1..65535";
        }
        must "(/ios:native/ios:router/ios-ospf:router-ospf/ios-ospf:ospf/ios-ospf:process-id[ios-ospf:id=current()]) or (/ios:native/ios:router/ios-ospf:router-ospf/ios-ospf:ospf/ios-ospf:process-id-vrf[ios-ospf:id=current()])" {
          error-message "configure router ospf first";
        }
      }
      list area {
        key "area-id";
        max-elements "1";
        leaf area-id {
          description
            "Set the OSPF area ID";
          type ios-types:ospf-area-type;
        }
        leaf secondaries {
          description
            "Include or exclude secondary IP addresses";
          type enumeration {
            enum "none";
          }
        }
      }
    }
  }

  grouping config-ospf-interface-retransmit-interval-grouping {
    leaf retransmit-interval {
      description
        "Time between retransmitting lost link state advertisements";
      type uint32 {
        range "1..65535";
      }
      default "5";
      units "seconds";
    }
  }

  grouping config-ospf-interface-resync-timeout-grouping {
    leaf resync-timeout {
      description
        "Interval after which adjacency is reset if oob-resync is not started";
      type uint32 {
        range "1..65535";
      }
      default "40";
    }
  }

  grouping config-ospf-interface-shutdown-grouping {
    leaf shutdown {
      description
        "Set OSPF protocol's state to disable under current interface";
      type empty;
    }
  }

  grouping config-ospf-interface-transmit-delay-grouping {
    leaf transmit-delay {
      description
        "Link state transmit delay";
      type uint32 {
        range "1..65535";
      }
      default "1";
    }
  }

  grouping config-ospf-interface-ttl-security-grouping {
    container ttl-security {
      description
        "TTL security check";
      presence "true";
      choice ttl-security-choice {
        leaf disable {
          description
            "disable TTL security check";
          type empty;
        }
        leaf hops {
          description
            "IP hops";
          type uint8 {
            range "1..254";
          }
        }
      }
    }
  }

  grouping config-ospf-interface-affinity-grouping {
    container affinity {
      description
        "Affinity configuration on interface";
      container flex-algo {
        description
          "Affinity flex-algo configuration on interface";
        leaf-list name {
          description
            "Affinity name";
          type string {
            length "1..32";
          }
        }
      }
    }
  }

  grouping config-ospf-interface-ip-ospf-grouping {
    container router-ospf {
      description
        "Interface Commands for OSPF IPv4";
      container ospf {
        description
          "OSPF interface commands";
        uses config-ospf-interface-process-id-igrouping;
        uses config-ospf-interface-adjacency-grouping;
        uses config-ospf-interface-authentication-grouping;
        uses config-ospf-interface-authentication-key-grouping;
        uses config-ospf-interface-bfd-grouping;
        uses config-ospf-interface-cost-grouping;
        uses config-ospf-interface-database-filter-grouping;
        uses config-ospf-interface-dead-interval-grouping;
        uses config-ospf-interface-demand-circuit-grouping;
        uses config-ospf-interface-fast-reroute-grouping;
        uses config-ospf-interface-flood-reduction-grouping;
        uses config-ospf-interface-hello-interval-grouping;
        uses config-ospf-interface-lls-ip-grouping;
        uses config-ospf-interface-message-digest-key-grouping;
        uses config-ospf-interface-mtu-ignore-grouping;
        uses config-ospf-interface-multi-area-grouping;
        uses config-ospf-interface-network-ip-grouping;
        uses config-ospf-interface-prefix-suppression-grouping;
        uses config-ospf-interface-priority-common-grouping;
        uses config-ospf-interface-resync-timeout-grouping;
        uses config-ospf-interface-retransmit-interval-grouping;
        uses config-ospf-interface-shutdown-grouping;
        uses config-ospf-interface-transmit-delay-grouping;
        uses config-ospf-interface-ttl-security-grouping;
        uses config-ospf-interface-delay-normalize-grouping;
        uses config-ospf-interface-affinity-grouping;
        uses config-ospf-packet-size-grouping;
      }
    }
  }

  grouping config-ospf-message-digest-key-grouping {
    list message-digest-key {
      description
        "Set message digest key";
      key "id";
      leaf id {
        description
          "Key ID";
        type uint8 {
          range "1 .. 255";
        }
      }
      container md5 {
        description
          "Use MD5 algorithm";
        leaf auth-type {
          description
            "Encryption type (0 for not yet encrypted, 7 for proprietary)";
          type uint8 {
            range "0 .. 7";
          }
        }
        leaf auth-key {
          description
            "Authentication key (16 chars)";
          type string {
            length "1 .. 16";
          }
        }
      }
    }
  }

  grouping config-ospf-router-sub-mode-common-grouping {
    uses config-ospf-adjacency-grouping;
    uses config-ospf-area-grouping;
    uses config-ospf-auto-cost-grouping;
    uses config-ospf-autoroute-exclude-grouping;
    uses config-ospf-bfd-grouping;
    uses config-ospf-compatible-grouping;
    uses config-ospf-default-information-grouping;
    uses config-ospf-default-metric-grouping;
    uses config-ospf-discard-route-grouping;
    uses config-ospf-distance-grouping;
    uses config-ospf-distribute-list-grouping;
    uses config-ospf-domain-id-grouping;
    uses config-ospf-domain-tag-grouping;
    uses config-ospf-ignore-grouping;
    uses config-ospf-interface-id-grouping;
    uses config-ospf-limit-grouping;
    uses config-ospf-local-rib-criteria-grouping;
    uses config-ospf-log-adjacency-changes-grouping;
    uses config-ospf-max-lsa-grouping;
    uses config-ospf-max-metric-grouping;
    uses config-ospf-maximum-paths-grouping;
    uses config-ospf-microloop-grouping;
    uses config-ospf-mpls-grouping;
    uses config-ospf-multicast-intact-grouping;
    uses config-ospf-neighbor-grouping;
    uses config-ospf-network-grouping;
    uses config-ospf-nsf-grouping;
    uses config-ospf-nsr-grouping;
    uses config-ospf-queue-depth-grouping;
    uses config-ospf-passive-interface-grouping;
    uses config-ospf-prefix-priority-grouping;
    uses config-ospf-prefix-suppression-grouping;
    uses config-ospf-priority-grouping;
    uses config-ospf-process-min-time-grouping;
    uses config-ospf-redistribute-grouping;
    uses config-ospf-router-id-grouping;
    uses config-ospf-shutdown-grouping;
    uses config-ospf-snmp-grouping;
    uses config-ospf-summary-address-grouping;
    uses config-ospf-table-map-grouping;
    uses config-ospf-timers-grouping;
    uses config-ospf-traffic-share-grouping;
    uses config-ospf-ttl-security-grouping;
    uses config-ospf-packet-size-grouping;
  }

  grouping config-ospf-router-sub-mode-grouping {
    uses config-ospf-router-sub-mode-common-grouping;
    uses config-ospf-capability-grouping;
    uses config-ospf-fast-reroute-grouping;
    uses config-ospf-flex-algo-grouping;
    uses config-ospf-affinity-map-grouping;
  }

  grouping config-ospf-router-sub-mode-vrf-grouping {
    uses config-ospf-router-sub-mode-common-grouping;
    uses config-ospf-capability-vrf-grouping;
  }

  grouping config-ospf-router-grouping {
    container router-ospf {
      description
        "Router OSPF";
      container ospf {
        description
          "Router OSPF";
        list process-id {
          description
            "Open Shortest Path First (OSPF)";
          key "id";
          leaf id {
            description
              "Process ID";
            type uint16 {
              range "1..65535";
            }
            must "not (../../process-id-vrf[id=current()])" {
              error-message "process-id current() already comfigured under vrf";
            }
          }
          uses config-ospf-router-sub-mode-grouping;
        }
        list process-id-vrf {
          description
            "Open Shortest Path First (OSPF)";
          key "id vrf";
          leaf id {
            description
              "Process ID";
            type uint16 {
              range "1..65535";
            }
            must "not (../../process-id[id=current()])" {
              error-message "process-id current() already comfigured under global";
            }
          }
          leaf vrf {
            description
              "VPN Routing/Forwarding Instance";
            must "(/ios:native/ios:vrf/ios:definition[ios:name=current()] and /ios:native/ios:vrf/ios:definition[ios:name=current()]/ios:address-family/ios:ipv4) or /ios:native/ios:ip/ios:vrf[ios:name=current()]" {
              error-message "ipv4 VRF must be created 1st, deleted last";
            }
            type string;
          }
          uses config-ospf-router-sub-mode-vrf-grouping;
        }
      }
    }
  }

  augment "/ios:native/ios:router" {
    uses config-ospf-router-grouping;
    uses config-router-ospf-grouping {
      status obsolete;
    }
  }
  augment "/ios:native/ios:interface/ios:Ethernet/ios:ip" {
    uses config-ospf-interface-ip-ospf-grouping;
    uses config-interface-ip-ospf-grouping {
      status obsolete;
    }
  }
  augment "/ios:native/ios:interface/ios:FastEthernet/ios:ip" {
    uses config-ospf-interface-ip-ospf-grouping;
    uses config-interface-ip-ospf-grouping {
      status obsolete;
    }
  }
  augment "/ios:native/ios:interface/ios:GigabitEthernet/ios:ip" {
    uses config-ospf-interface-ip-ospf-grouping;
    uses config-interface-ip-ospf-grouping {
      status obsolete;
    }
  }
  augment "/ios:native/ios:interface/ios:TenGigabitEthernet/ios:ip" {
    uses config-ospf-interface-ip-ospf-grouping;
    uses config-interface-ip-ospf-grouping {
      status obsolete;
    }
  }
  augment "/ios:native/ios:interface/ios:FiveGigabitEthernet/ios:ip" {
    uses config-ospf-interface-ip-ospf-grouping;
    uses config-interface-ip-ospf-grouping {
      status obsolete;
    }
  }
  augment "/ios:native/ios:interface/ios:AppGigabitEthernet/ios:ip" {
    uses config-ospf-interface-ip-ospf-grouping;
    uses config-interface-ip-ospf-grouping {
      status obsolete;
    }
  }
  augment "/ios:native/ios:interface/ios:TwentyFiveGigE/ios:ip" {
    uses config-ospf-interface-ip-ospf-grouping;
    uses config-interface-ip-ospf-grouping {
      status obsolete;
    }
  }
  augment "/ios:native/ios:interface/ios:TwoGigabitEthernet/ios:ip" {
    uses config-ospf-interface-ip-ospf-grouping;
    uses config-interface-ip-ospf-grouping {
      status obsolete;
    }
  }
  augment "/ios:native/ios:interface/ios:FortyGigabitEthernet/ios:ip" {
    uses config-ospf-interface-ip-ospf-grouping;
    uses config-interface-ip-ospf-grouping {
      status obsolete;
    }
  }
  augment "/ios:native/ios:interface/ios:HundredGigE/ios:ip" {
    uses config-ospf-interface-ip-ospf-grouping;
    uses config-interface-ip-ospf-grouping {
      status obsolete;
    }
  }
  augment "/ios:native/ios:interface/ios:Port-channel/ios:ip" {
    uses config-ospf-interface-ip-ospf-grouping;
    uses config-interface-ip-ospf-grouping {
      status obsolete;
    }
  }
  augment "/ios:native/ios:interface/ios:Port-channel-subinterface/ios:Port-channel/ios:ip" {
    uses config-ospf-interface-ip-ospf-grouping;
    uses config-interface-ip-ospf-grouping {
      status obsolete;
    }
  }
  augment "/ios:native/ios:interface/ios:Loopback/ios:ip" {
    uses config-ospf-interface-ip-ospf-grouping;
    uses config-interface-ip-ospf-grouping {
      status obsolete;
    }
  }
  augment "/ios:native/ios:interface/ios:Serial/ios:ip" {
    uses config-ospf-interface-ip-ospf-grouping;
    uses config-interface-ip-ospf-grouping {
      status obsolete;
    }
  }
  augment "/ios:native/ios:interface/ios:Tunnel/ios:ip" {
    uses config-ospf-interface-ip-ospf-grouping;
    uses config-interface-ip-ospf-grouping {
      status obsolete;
    }
  }
  augment "/ios:native/ios:interface/ios:BDI/ios:ip" {
    uses config-ospf-interface-ip-ospf-grouping;
    uses config-interface-ip-ospf-grouping {
      status obsolete;
    }
  }
  augment "/ios:native/ios:interface/ios:Vlan/ios:ip" {
    uses config-ospf-interface-ip-ospf-grouping;
    uses config-interface-ip-ospf-grouping {
      status obsolete;
    }
  }
  augment "/ios:native/ios:interface/ios:Dialer/ios:ip" {
    uses config-ospf-interface-ip-ospf-grouping;
    uses config-interface-ip-ospf-grouping {
      status obsolete;
    }
  }
  augment "/ios:native/ios:interface/ios:BD-VIF/ios:ip" {
    uses config-ospf-interface-ip-ospf-grouping;
    uses config-interface-ip-ospf-grouping {
      status obsolete;
    }
  }
  augment "/ios:native/ios:interface/ios:Ethernet/ios:ipv6" {
    uses config-interface-ipv6-ospf-grouping {
      status obsolete;
    }
  }
  augment "/ios:native/ios:interface/ios:FastEthernet/ios:ipv6" {
    uses config-interface-ipv6-ospf-grouping {
      status obsolete;
    }
  }
  augment "/ios:native/ios:interface/ios:GigabitEthernet/ios:ipv6" {
    uses config-interface-ipv6-ospf-grouping {
      status obsolete;
    }
  }
  augment "/ios:native/ios:interface/ios:TenGigabitEthernet/ios:ipv6" {
    uses config-interface-ipv6-ospf-grouping {
      status obsolete;
    }
  }
  augment "/ios:native/ios:interface/ios:FiveGigabitEthernet/ios:ipv6" {
    uses config-interface-ipv6-ospf-grouping {
      status obsolete;
    }
  }
  augment "/ios:native/ios:interface/ios:AppGigabitEthernet/ios:ipv6" {
    uses config-interface-ipv6-ospf-grouping {
      status obsolete;
    }
  }
  augment "/ios:native/ios:interface/ios:TwentyFiveGigE/ios:ipv6" {
    uses config-interface-ipv6-ospf-grouping {
      status obsolete;
    }
  }
  augment "/ios:native/ios:interface/ios:TwoGigabitEthernet/ios:ipv6" {
    uses config-interface-ipv6-ospf-grouping {
      status obsolete;
    }
  }
  augment "/ios:native/ios:interface/ios:FortyGigabitEthernet/ios:ipv6" {
    uses config-interface-ipv6-ospf-grouping {
      status obsolete;
    }
  }
  augment "/ios:native/ios:interface/ios:HundredGigE/ios:ipv6" {
    uses config-interface-ipv6-ospf-grouping {
      status obsolete;
    }
  }
  augment "/ios:native/ios:interface/ios:Port-channel/ios:ipv6" {
    uses config-interface-ipv6-ospf-grouping {
      status obsolete;
    }
  }
  augment "/ios:native/ios:interface/ios:Loopback/ios:ipv6" {
    uses config-interface-ipv6-ospf-grouping {
      status obsolete;
    }
  }
  augment "/ios:native/ios:interface/ios:Tunnel/ios:ipv6" {
    uses config-interface-ipv6-ospf-grouping {
      status obsolete;
    }
  }
  augment "/ios:native/ios:interface/ios:BDI/ios:ipv6" {
    uses config-interface-ipv6-ospf-grouping {
      status obsolete;
    }
  }
  augment "/ios:native/ios:interface/ios:Vlan/ios:ipv6" {
    uses config-interface-ipv6-ospf-grouping {
      status obsolete;
    }
  }
  augment "/ios:native/ios:interface/ios:Dialer/ios:ipv6" {
    uses config-interface-ipv6-ospf-grouping {
      status obsolete;
    }
  }
  augment "/ios:native/ios:interface/ios:BD-VIF/ios:ipv6" {
    uses config-interface-ipv6-ospf-grouping {
      status obsolete;
    }
  }
}
